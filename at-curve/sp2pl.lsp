(defun @curve:spline2lwpl()
  (setq ent (entsel "\n选择一个样条曲线:"))
  (if ent
      (progn
	(setq layerName (cdr (ASSOC 8 (entget(car ent)))))
	(if (= 4 (logand 4 (cdr (assoc 70 (tblsearch "layer" layerName)))))
	    (exit)
	    )
	(if ent
	    (progn
	      (if(= (cdr (ASSOC 0 (entget(car ent)))) "SPLINE")
		 (progn
		   (initget 2 "Yes No")
		   (setq sta (getkword "\n要删除样条曲线吗? [是(Y)/否(N)]:"))
		   (setq obj (vlax-ename->vla-object (car ent)))
		   (setq bisclose (vlax-curve-isclosed (car ent)))
		   (setq param (vlax-curve-getEndParam obj))
		   (setq pntcount (vla-get-NumberOfControlPoints obj))
		   (setq segcount (getint (strcat "\n选择段数<" (rtos (* pntcount 8) 2 0) ">:")))
		   (if (not segcount) (setq segcount (* pntcount 8)))
		   (setq count (1+ segcount))
		   (if(< segcount 1) (exit))
		   (setq subparam (/ param segcount))
		   (if bisclose
		       (setq rblist (append '((0 . "LWPOLYLINE") (100 . "AcDbEntity") (67 . 0)
					      (100 . "AcDbPolyline")) (list (cons 90  (1+ count ))) '((70 . 1) (43 . 0.0) (38 . 0.0) (39 . 0.0))
					      (list (cons 10 (vlax-curve-getStartPoint obj)))
					      ))
		       (setq rblist (append '((0 . "LWPOLYLINE") (100 . "AcDbEntity") (67 . 0)
					      (100 . "AcDbPolyline")) (list (cons 90  (1+ count ))) '((70 . 0) (43 . 0.0) (38 . 0.0) (39 . 0.0))
					      (list (cons 10 (vlax-curve-getStartPoint obj)))
					      ))
		       )
		   (setq inp 1)
		   (setq segnpt 100)
		   (while (< inp count)
		     (setq subcount (min segnpt (- count inp)))
		     (setq subrblist nil)
		     (repeat subcount
			     (setq vex (vlax-curve-getPointAtParam obj subparam))
			     (setq subrblist (append subrblist (list (cons 10 vex))))
			     (setq subparam (+ subparam (/ param segcount)))
			     )
		     (setq rblist (append rblist subrblist))
		     (setq inp (+ inp subcount))
		     )
		   (setq rblist (append rblist  '((210 0.0 0.0 1.0))))
		   (if(not (entmake rblist)) (exit))
		   (if(not (setq pl (entlast)))(exit))
		   (setq pl-obj (vlax-ename->vla-object pl))
		   (if (= sta "Yes")
		       (entdel (car ent))
		       )
		   )
		 (print "选择的不是样条曲线!") 
		 )
	      )
	    )
	(princ)
	)))
