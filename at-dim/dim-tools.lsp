;;; ================================================================
;;; 标注修复工具（源自 Paracadd.com，重构为 @dim: 命名空间）
;;; ================================================================

;;; 修复标注/引线/直线的Z坐标（压平到Z=0）
(defun @dim:fixdims (/ ss idx ent enx)
  (setq ss (ssget "X" '((-4 . "<OR")
                          (0 . "DIMENSION")
                          (0 . "LEADER")
                          (0 . "LINE")
                         (-4 . "OR>"))))
  (if ss
    (progn
      (setq idx 0)
      (while (< idx (sslength ss))
        (setq ent (ssname ss idx)
              enx (entget ent))
        (setq enx (subst (cons 10 (list (cadr (assoc 10 enx))
                                        (caddr (assoc 10 enx)) 0.0))
                         (assoc 10 enx) enx))
        (setq enx (subst (cons 11 (list (cadr (assoc 11 enx))
                                        (caddr (assoc 11 enx)) 0.0))
                         (assoc 11 enx) enx))
        (if (or (= "DIMENSION" (cdr (assoc 0 enx)))
                (= "LEADER" (cdr (assoc 0 enx))))
          (progn
            (setq enx (subst (cons 12 (list (cadr (assoc 12 enx))
                                            (caddr (assoc 12 enx)) 0.0))
                             (assoc 12 enx) enx))
            (setq enx (subst (cons 13 (list (cadr (assoc 13 enx))
                                            (caddr (assoc 13 enx)) 0.0))
                             (assoc 13 enx) enx))
            (setq enx (subst (cons 14 (list (cadr (assoc 14 enx))
                                            (caddr (assoc 14 enx)) 0.0))
                             (assoc 14 enx) enx))
            (setq enx (subst (cons 15 (list (cadr (assoc 15 enx))
                                            (caddr (assoc 15 enx)) 0.0))
                             (assoc 15 enx) enx))
            (setq enx (subst (cons 16 (list (cadr (assoc 16 enx))
                                            (caddr (assoc 16 enx)) 0.0))
                             (assoc 16 enx) enx))))
        (entmod enx)
        (setq idx (1+ idx)))
      (princ (strcat "\n已修复 " (itoa (sslength ss)) " 个对象。")))
    (princ "\n未找到需要修复的对象。"))
  (princ))

;;; 切换标注延伸线
(defun @dim:dimext (/ option ent enx obj)
  (vl-load-com)
  (initget "1st 2nd Both None")
  (setq option (getkword "\n选择要关闭的延伸线 [1st/2nd/Both/None] <Both>: "))
  (if (null option) (setq option "Both"))
  (while (setq ent (entsel "\n选择标注: "))
    (if (and ent (= "DIMENSION" (cdr (assoc 0 (entget (car ent))))))
      (progn
        (setq obj (vlax-ename->vla-object (car ent)))
        (cond
          ((member option '("1st" "First"))
           (vlax-put-property obj 'ExtLine1Suppress -1)
           (vlax-put-property obj 'ExtLine2Suppress 0))
          ((member option '("2nd" "Second"))
           (vlax-put-property obj 'ExtLine1Suppress 0)
           (vlax-put-property obj 'ExtLine2Suppress -1))
          ((member option '("Both" "All"))
           (vlax-put-property obj 'ExtLine1Suppress -1)
           (vlax-put-property obj 'ExtLine2Suppress -1))
          ((= option "None")
           (vlax-put-property obj 'ExtLine1Suppress 0)
           (vlax-put-property obj 'ExtLine2Suppress 0)))))
    (princ "\n未选中有效标注。"))
  (princ))
