(defun @layout:pvp-v (/ clayout vps)
  (@::prompt "视口坐标随视图")
  (setq clayout (getvar "ctab"))
   (setvar "cmdecho" 0)
  (foreach layout (layout:list)
	   (setvar "ctab" layout)
	   (setq vps (pickset:to-list
		      (ssget"x"
			    (list '(0 . "viewport")
				  (cons 410 layout)
				  '(-4 . "<NOT")
				  '(69 . 1)
				  '(-4 . "NOT>")
				  '(-4 . ">")
				  '(40 . 20)
				  ))))
	   (@:cmd "zoom" "a")
	   (foreach vpid (mapcar '(lambda(x)
				    (entity:getdxf x 69))
				 vps)
		    (@:cmd"mspace")(setvar "cvport" vpid)(@:cmd"ucs""v")
		    ))
  (setvar"ctab" clayout)
  (@:cmd"pspace")
  (setvar "cmdecho" 1)

  )

(defun @layout:pvp-w (/ clayout vps)
  (@::prompt "视口坐标随视图")
  (setq clayout (getvar "ctab"))
  (setvar "cmdecho" 0)
  (foreach layout (layout:list)
	   (setvar "ctab" layout)
	   (setq vps (pickset:to-list
		      (ssget"x"
			    (list '(0 . "viewport")
				  (cons 410 layout)
				  '(-4 . "<NOT")
				  '(69 . 1)
				  '(-4 . "NOT>")
				  '(-4 . ">")
				  '(40 . 20)))))
	   (@:cmd "zoom" "a")
	   (foreach vpid (mapcar '(lambda(x)
				    (entity:getdxf x 69))
				 vps)
		    (@:cmd"mspace")(setvar "cvport" vpid)(@:cmd"ucs""w")
		    ))
  (setvar"ctab" clayout)
  (@:cmd"pspace")
  (setvar "cmdecho" 1)
  )
(defun @layout:pvp-ma ()
  (@::prompt "将选中的视口的冻结图层设置刷到其它视口。")
  (@:prompt "请点选源视口:")
  (if (setq src-layout (ssget "_:S:E" '((0 . "VIEWPORT"))))
      (progn
	(setq obj-vflayers
	      (vla-getxdata (e2o (ssname src-layout 0))
			    "" 'xtypeOut 'xdataOut))
	(@:skip-speak)
	(@:prompt "请框选择目标视口:")
	
	(if (setq dist-layouts (ssget '((0 . "VIEWPORT"))))
	    ;;清除原来的冻结状态
	    (progn
	      (@:cmd "vplayer" "t" "*" "S" dist-layouts "" "")
	      (foreach dst (pickset:to-list dist-layouts)
		       
		       (vla-setXdata (e2o dst)
				     xtypeOut xdataOut)
		       (vla-display (e2o dst) :vlax-false)
		       (vla-display (e2o dst) :vlax-true)
		       ;;(vla-syncmodelview (e2o dst))
		       (vla-update (e2o dst))
		       ))
	  (@:speak "没有选中目标视口,退出执行。")
	  ))
    (@:speak "没有选中源视口,退出执行。")
    ))
