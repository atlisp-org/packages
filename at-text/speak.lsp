(defun @text:menu-speak ()
  (prompt "璇烽€夋嫨瑕佹湕璇荤殑鏂囨湰:")
  (setq texts (ssget '((0 . "*text,ACAD_TABLE,TCH_DRAWINGNAME"))))
  (setq texts (pickset:sort
	       (pickset:to-list texts)
	       "Yx" 0))
  (@:set-config '@::speak-asynchronous 0)
  (redraw)
  (foreach text texts
	   (sssetfirst nil (ssadd text))
	   (redraw)
	   (redraw text 3)
	   (sleep 0.5)
	   (@:speak (text:remove-fmt (text:get-mtext text))))
  (@:set-config '@::speak-asynchronous 1)
  (princ)
  )
