;; ((-1 . <图元名: 7ff4fbc2fda0>)
;; (0 . TCH_DRAWINGNAME) (330 . <图元名: 7ff4fbc2e970>) (5 . 33A) (100 . AcDbEntity) (67 . 0) (410 . Model) (8 . DIM_SYMB) (100 . TDbEntity) (46 . 0.0) (47 . 100.0) (68 . 0) (100 . TDbDrawingName) (70 . 3) (10 0.0 0.0 0.0) (1 . 天正图名标注输入) (2 . 1:100) (50 . 0.0) (40 . 7.0) (41 . 5.0) (42 . 0.7) (43 . 0.6) (340 . <图元名: 7ff4fbc2e920>) (341 . <图元名: 7ff4fbc2e920>) (290 . 1) (71 . 1))
;; 天正通用组码
;;  47 出图比例
(defun tch:help ()
  (@:help (strcat
	   "天正通用组码\n"
	   "47 出图比例\n"
	   "天正图名信息，dxf 1 图名，2 比例\n"


	   )))

(defun tch:getbox (obj)
  nil)
