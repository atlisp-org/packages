;;;下面程序用以获得椭圆的变换矩阵。
(defun Mat:GetEllipseTransMatrix (e / dxf Nrm Cen Maj Mnr ptb DX DY DZ mat)        
  (defun AppendToMatrix (mat org)
    (append
      (mapcar 'append mat (mapcar 'list org))
      '((0. 0. 0. 1.))
    )
  )

  (setq dxf (entget e))
  (setq Nrm (cdr (assoc 210 dxf)))
  (setq Cen (cdr (assoc 10 dxf)))
  (setq Maj (cdr (assoc 11 dxf)))
  (setq PtB (vlax-curve-getPointAtParam e (/ pi 2)))
  (setq Mnr (mapcar '- ptb cen))
  (setq DX  (Mat:unit Maj))
  (setq DY  (Mat:unit Mnr))
  (setq DZ  (Mat:unit Nrm))
  (setq mat (list DX DY DZ))
  (list
    (AppendToMatrix mat (mapcar '- (Mat:mxv mat cen)))        ;WCS->OCS 由世界坐标系变换到物体坐标系
    (AppendToMatrix (Mat:trp mat) cen)                        ;OCS->WCS 由物体坐标系变换到世界坐标系
  )
)
;;;以下为测试程序
(defun c:test1 (/ sel ent mat obj doc)
  (if (setq sel (ssget ":S" '((0 . "ELLIPSE"))))
    (progn
      (setq doc (vla-get-ActiveDocument (vlax-get-acad-object)))
      (vla-StartUndoMark doc)
      (setq ent (ssname sel 0))
      (setq mat (Mat:GetEllipseTransMatrix ent))
      (setq obj (vlax-ename->vla-object ent))
      (vla-transformby obj (vlax-tmatrix (car mat)))
      (command "Select" ent pause)
      (vla-transformby obj (vlax-tmatrix (cadr mat)))
      (vla-EndUndoMark doc)
      (princ)
    )
  )
)

;;;=====================================================
;;;功能: 画一个椭圆或者椭圆弧                             
;;;参数: 中心，长轴，短轴和旋转角度，起始角度，终点角度 
;;;返回: 一个椭圆实体                                   
;;;=====================================================
(defun Make-Ellipse (cen a b ang an1 an2 / m n an)
  (if (> b a)
    (setq m b n a an (+ ang (/ pi 2)))
    (setq m a n b an ang)
  )
  (entmakeX
    (list
      '(0 . "ELLIPSE")
      '(100 . "AcDbEntity")
      '(100 . "AcDbEllipse")
      (cons 10 cen)
      (cons 11 (polar '(0. 0. 0.) an m))
      (cons 40 (/ n m 1.0))
      (cons 41 an1)
      (cons 42 an2)
    )
  )
  )

(defun ELL:5PEllipse (p1 p2 p3 p4 p5 / p12 p23 p34 p45 t2 t3 t4 t23 t34 t45 cen)
  (setq p12 (inters p5 p1 p2 p3 nil))
  (setq p23 (inters p1 p2 p3 p4 nil))
  (setq p34 (inters p2 p3 p4 p5 nil))
  (setq p45 (inters p3 p4 p5 p1 nil))
  (setq t2  (inters p12 p23 p4 p5 nil))
  (setq t3  (inters p23 p34 p5 p1 nil))
  (setq t4  (inters p34 p45 p1 p2 nil))
  (setq t23 (inters t2 p2 t3 p3 nil))
  (setq t34 (inters t3 p3 t4 p4 nil))
  (setq m23 (midpt p2 p3))
  (setq m34 (midpt p3 p4))
  (setq cen (inters t23 m23 t34 m34 nil))
  (Mat:C3P-Ellipse cen p2 p3 p4)
)
(defun midpt (p1 p2)
  (mapcar (function (lambda (x) (* x 0.5))) (mapcar '+ p1 p2))
)
(defun c:test5 (/ p1 p2 p3 p4 p5 ret)
  (initget 1)
  (setq p1 (getpoint "\n输入第一点:"))
  (initget 1)
  (setq p2 (getpoint "\n输入第二点:"))
  (initget 1)
  (setq p3 (getpoint "\n输入第三点:"))
  (initget 1)
  (setq p4 (getpoint "\n输入第四点:"))
  (initget 1)
  (setq p5 (getpoint "\n输入第五点:"))
  (setq ret (ELL:5PEllipse p1 p2 p3 p4 p5))
  (apply 'Ell:Make-Ellipse ret)
  (princ)
)
