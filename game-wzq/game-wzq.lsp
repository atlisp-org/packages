;;;;;;;;;;;;;;;;;;;;;;;;;;;;;;;;;;;;;;;;;;;;;;;;;;;;;;;;;;;;;;;;;;;;;;;;;;;;;;;;
;; 这是使用开发工具 dev-tools 自动创建的程序源文件 
;;;;;;;;;;;;;;;;;;;;;;;;;;;;;;;;;;;;;;;;;;;;;;;;;;;;;;;;;;;;;;;;;;;;;;;;;;;;;;;;
;; 定义配置项 'game-wzq:first 用于 应用包 game-wzq 的 第一个配置项 first 
;;(@:define-config 'game-wzq:first "我是配置项 game-wzq:first 的值" "这个配置项的用途说明。")
;; (@:get-config 'game-wzq:first) ;; 获取配置顶的值
;; (@:set-config 'game-wzq:first  "新设的值") ;; 设置配置顶的值
;; 向系统中添加菜单 
(@:add-menu "游戏" "五子棋" "(game-wzq:start)" )
(defun game-wzq:start ()
  (@:help (strcat "这里的内容用于在运行这个功能开始时，对用户进行功能提示。\n"
		  "如怎么使用，注意事项等。\n当用户设置了学习模式时，会在命令行或弹窗进行提示。\n"
		  ))
  ;; 以下部分为你为实现某一功能所编写的代码。
  (@:load "game-wzq/wzq")
  (C:wzq)
  (princ)
  )
