;;; 能过部件号KEY应能唯一确认一个部件，索引外部部件数据库得到该部件的尺寸信息及材料统计信息
;;; 部件号KEY 通过模板实现自动更新 更新时使用的属性由部件从属路径提供
(defun psk-path-wallthick (comp / pn r w)
  (cond ((= "DUCT-RECT" (psk-comp-gettype comp))
         (setq w (p-get comp "W"))
        )
        ((= "DUCT-ROUND" (psk-comp-gettype comp))
         (setq w (p-get comp "D"))
        )
        ((= "PIPE" (psk-comp-gettype comp))
         (setq w (p-get comp "DN"))
        )
  )
  (setq pn (p-get comp "PN"))
  (if (p-string-empty? pn)
    (if (wcmatch (p-get comp "SERV") "SE,EA(SE)")
      (setq pn "P3")
      (setq pn "P1")
    )
  )
  (setq r (p-lookup3 w
                     $psk-steelductwallthick
                     '("D" "P1" "P2" "P3" "P4")
          )
  )
  (p-get r pn)
)
(defun psk-comp-getbom (comp / wtk)
  (cond
    ((= "PATH" (psk-comp-getname comp))
     (cond ((= "DUCT-RECT" (psk-comp-gettype comp))
            (setq wtk (psk-path-wallthick comp))
            (psk-comp-set comp (cons "WTK" wtk))
            (list (p-dxf (psk-comp-getename comp) 5)
                  "矩形风管"
                  (p-get comp "W")
                  (p-get comp "H")
                  wtk
                  (psk-path-getlength comp)
            )
           )
           ((= "DUCT-ROUND" (psk-comp-gettype comp))
            (setq wtk (psk-path-wallthick comp))
            (psk-comp-set comp (cons "WTK" wtk))
            (list (p-dxf (psk-comp-getename comp) 5)
                  "圆形风管"
                  (p-get comp "D")
                  nil
                  wtk
                  (psk-path-getlength comp)
            )
           )
           ((= "PIPE" (psk-comp-gettype comp))
            (list (p-dxf (psk-comp-getename comp) 5)
                  "管道"
                  (p-get comp "DN")
                  nil
                  (p-get comp "WTK")
                  (psk-path-getlength comp)
            )
           )
     )
    )
;;;    ((= "FIT" (psk-comp-getname comp))
;;;     (setq tp (psk-comp-gettype comp))
;;;     (cond ((= "ELBOW" tp)
;;;	   )
;;;	   ((= "REDUCER" tp)
;;;	   )
;;;	   ((= "TEE" tp)
;;;	   )
;;;	   ((= "TEE-S" tp)
;;;	   )
;;;	   ((= "BRANCH" tp)
;;;	   )
;;;	   ((= "CROSS" tp)
;;;	   )
;;;     )
;;;    )
  )
)
(defun p-stringfy (lst /)
  (mapcar (function (lambda (e)
                      (if (null e)
                        ""
                        (vl-princ-to-string e)
                      )
                    )
          )
          lst
  )
)
;;;(defun p-write-line (lst)
;;;  ()
;;;)
(defun p-list->file (lst filename / f file)
  (setq file (vl-filename-mktemp filename)
        f    (open file "w")
  )
  (foreach e lst
    (if e
      (write-line e f)
    )
  )
  (close f)
  (startapp "notepad" file)
)
(defun psk-comps-getbom (comps / r)
  (foreach comp comps
    (setq r
           (cons (p-string-connect (p-stringfy (psk-comp-getbom comp)) "\t")
                 r
           )
    )
  )
  (setq r (cons (p-string-connect '("ID" "NAME" "W/D/DN" "H" "WTK" "L") "\t") r))
  (p-list->file r "bom.csv")
)
