(defun c:ar ()
  (p-commandrun '(psk-editor-createpath))
)
(defun c:pipe ()
  (p-commandrun '(psk-editor-createpipe))
)
(defun c:pskpg1 ()
  (p-commandrun '(psk-create-pipegroup '("CHS" "CHR" "CD") 300))
)
(defun c:pskpg2 ()
  (p-commandrun '(psk-create-pipegroup '("REF" "CD") 300))
)
(defun c:duct ()
  (p-commandrun '(psk-editor-createduct))
)
(defun c:ductr ()
  (p-commandrun '(psk-editor-createductr))
)
(defun c:cx ()
  (p-commandrun '(psk-comps-modify))
)
(defun c:er ()
  (p-commandrun '(psk-comps-modify))
)
(defun c:dc ()
  (p-commandrun '(psk-paths-connect (psk-paths-pick 4) t))
)

(defun c:ce ()
  (p-commandrun '(psk-connect-ports))
)

(defun c:ikp ()
  (p-commandrun
    '(psk-keypack-createinpath
      (psk-paths-pick 1)
      "AXIAL-FAN-GROUP"
     )
  )
)

(defun c:pskconfig ()
  (p-commandrun '(psk-settings-change))
)

(defun c:dr (/)
  (p-commandrun '(psk-cmd-redraw))
)
;;;(defun c:bzsb ()
;;;  (p-commandrun '(psk-cmd-idenequip))
;;;)
(defun c:bz ()
  (p-commandrun '(psk-cmd-iden))
)
(defun c:zbz ()
  (p-commandrun '(psk-pipegroup-iden))
)
(defun c:zhbz ()
  (p-commandrun '(psk-pipegroup-iden))
)

(setq $psk-last-flr 500.)
;;;(defun c:sumbranchs ()
;;;  (p-commandrun '(psk-path-sum (psk-comp-buildmap (psk-comps-all) (getpoint)) (p-edit-value "输入末端流量" $psk-last-flr)))
;;;)

(defun movepath	(resize / en pf pt)
  (if (and (setq en (car (entsel)))
	   (setq pf (trans (getpoint "指定管口") 1 0))
	   (setq pt (trans (getpoint pf "指定管口的新位置") 1 0))
      )
    (progn
      (psk-path-moveport en pf pt resize)
      (psk-comp-redraw (psk-comp-load en))
    )
  )
)
(defun c:movepath ()
  (p-commandrun '(movepath nil))
)
(defun c:movepathresize	()
  (p-commandrun '(movepath t))
)

(defun c:vrfbranch (/)
  (p-commandrun '(psk-vrf-branchs (psk-paths-pick 2)))
)
(defun c:pskflr	(/)
  (p-commandrun '(psk-batch-cld->flr))
)

(defun c:pskdn (/)
  (setq r (p-confirm "重置管道DN" "N"))
  (if (= r "Y")
    (setq r t)
    (setq r nil)
  )
  (p-commandrun '(psk-batch-flr->dn r))
)

(defun c:showbranchs ()
  (p-commandrun '(psk-show-branchs (cadr (psk-path-pickend))))
)

(defun c:largestbranch (/)
  (p-commandrun
    '(psk-show-largestbranch (cadr (psk-path-pickend)))
  )
)
(defun c:tot (/)
  (p-commandrun '(psk-path-total))
)

(defun c:sljs (/)
  (p-commandrun '(psk-totalandcalc))
)

(defun c:pskfhll (/)
  (p-commandrun '(psk-batch-cld->flr))
)
(defun c:pskcalcddn (/)
  (p-commandrun '(psk-cld->cddn))
)
(defun c:pskcalrefpipesize (/)
  (p-commandrun '(psk-cld->coppersize))
)
(defun c:pskfgkd (/)
  (p-commandrun '(psk-batch-flr->w))
)
(defun c:pskfgzl (/)
  (p-commandrun '(psk-batch-cmh->prl))
)
(defun c:compexport (/)
  (p-commandrun
    '(psk-analysis-export
      (psk-comps-ssget)
      '(".TYPE"	"SERV" "W" "H" "D" "DN"	"WTK" "CLD" "FLR" ".FLV" ".PM"
	".PRL")
     )
  )
)
(defun c:bom ()
  (p-commandrun '(psk-comps-getbom (psk-comps-ssget)))
)


(defun c:pskabout ()
  (pdb-dlg-show
    (psk-get-filename "dialogs.dcl")
    "aboutDialog"
    (lambda ()
      (pdb-list-fill
	"LIST"
	(p-file-read (psk-get-filename "readme.txt"))
      )
    )
    nil
  )
)
