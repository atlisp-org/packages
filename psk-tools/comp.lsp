(defun psk-comp-getname	(comp /)
  (p-get comp ".CLASS")
)

(defun psk-comp-gettype	(comp /)
  (p-get comp ".TYPE")
)

(defun psk-comp-getename (comp /)
  (p-get comp -1)
)

;; (psk-comp-save '(("SERV" . "OA") ("W" . 500) ("H" . 320)) (car (entsel)) "PSK-FIT")
(defun psk-comp-save (comp ename appid /)
  (if ename
    (p-xprop-set
      ename
      appid
      (vl-remove-if
	(function (lambda (e) (member (car e) '(-1 ".CLASS"))))
	comp
      )
    )
  )
)
;;

;; (psk-comp-load (car (entsel)))
;; ((-1 . <图元名: 7ff47770d020>) ("CLASS" . "PATH") ("TYPE" . "RECTANGULAR") ("SERV" . "OA") ("W" . 500) ("H" . 320))
(defun psk-comp-load (ename / x xdata)
  (setq xdata (p-xdata-all ename))

  (cond	((setq x (p-get xdata "PSK-PATH"))
	 (append (list (cons -1 ename) (cons ".CLASS" "PATH"))
		 (p-xprop-unpack x)
	 )
	)
;;;	((setq x (p-get xdata "PSK-FIT"))
;;;	 (append (list (cons -1 ename) (cons ".CLASS" "FIT"))
;;;		 (p-xprop-unpack x)
;;;	 )
;;;	)
	((setq x (p-get xdata "PSK-PART"))
	 (append (list (cons -1 ename) (cons ".CLASS" "PART"))
		 (p-xprop-unpack x)
	 )
	)
        ((setq x (p-get xdata "PSK-PARTSET"))
	 (append (list (cons -1 ename) (cons ".CLASS" "PARTSET"))
		 (p-xprop-unpack x)
	 )
	)
	((setq x (p-get xdata "PSK-EQUIP"))
	 (append (list (cons -1 ename) (cons ".CLASS" "EQUIP"))
		 (p-xprop-unpack x)
	 )
	)
	(t
	 nil ;_相应的appid不存在时 ，不生成对象
	)
  )
)


;;;(defun psk-comp-getports (comp / name)
(defun psk-comp-set (en prop / xdata)
  ;; comp
  (if (vl-consp en)
    (setq en (psk-comp-getename en))
  )

  (setq xdata (p-xdata-all en))

  (cond ((p-get xdata "PSK-PATH")
         (p-xprop-set en "PSK-PATH" prop)
        )
;;;        ((p-get xdata "PSK-FIT")
;;;         (p-xprop-set en "PSK-FIT" prop)
;;;        )
        ((p-get xdata "PSK-PART")
         (p-xprop-set en "PSK-PART" prop)
        )
        ((p-get xdata "PSK-PARTSET")
         (p-xprop-set en "PSK-PARTSET" prop)
        )
        ((p-get xdata "PSK-EQUIP")
         (p-xprop-set en "PSK-EQUIP" prop)
        )
        (t
         (princ "\n无法设置对象属性")
         nil ;_相应的appid不存在时 ，不生成对象
        )
  )
)


;; (psk-comp-get (car (entsel)) "CLD")
(defun psk-comp-get (en keys)
;;;  (if (p-xdata-get en "PSK-FIT")
;;;    (p-xprop-get en "PSK-FIT" keys)
;;;    (p-xprop-get en "PSK-PATH" keys)
;;;  )
  (setq prop (psk-comp-load en))
  (p-get prop keys)
)

;; (psk-comp-getports (car (entsel)))
(defun psk-comp-getports (comp / name)
  (if (/= 'ename (type comp))
    (setq comp (psk-comp-getename comp))
  )
  (if (p-xdata-get comp "PSK-PORT")
    (psk-fit-getports comp)
    (if (p-xdata-get comp "PSK-PATH")
      (psk-path-getports comp)
    )
  )
)

(defun psk-comp-moveport (comp p newp /)
  (setq name (psk-comp-getname comp))
  (cond
    ((= "FIT" name)
     (psk-fit-moveport comp p newp)
    )
    ((= "PATH" name)
     (psk-path-moveport comp p newp t)
    )
  )
)
;;; (psk-comps-moveport (setq p (getpoint)) (getpoint p) (psk-comps-buildbst (psk-comps-all) 0.1) nil)
(defun psk-comps-moveport (p newp bst moved /)
  (if (null moved)
    (setq moved (ssadd))
  )
  (foreach comp	(p-bst-find p bst 0.1)
    (if	(not (ssmemb (p-get comp -1) moved))
      (progn
	(setq r	    (psk-comp-moveport comp p newp)
	      moved (ssadd (p-get comp -1) moved)
	)
	(if r
	  (progn
;;;	    (princ r)
	    (setq offset (car r)
		  r	 (cdr r)
	    )
	    (foreach p	r
	      (psk-comps-moveport p (mapcar '+ p offset) bst moved)
	    )
	  )
	)
      )
    )
  )
)
;;

;;;(setq $psk-appid-all )

(defun psk-ss->comps (ss)
  (mapcar 'psk-comp-load (p-ss->enames ss))
)
(defun psk-comps-ssget1 ()
  (ssget '((-3 ("PSK-PATH,PSK-PART,PSK-PARTSET,PSK-EQUIP"))))
)
(defun psk-ss-getduct ()
  (ssget '((-3 ("PSK-PATH,PSK-PART,PSK-PARTSET")) (8 . "M-*风管*")))
)
(defun psk-ss-getductpath ()
  (ssget '((-3 ("PSK-PATH")) (8 . "M-*风管*")))
)
(defun psk-ss-getpipe ()
  (ssget '((-3 ("PSK-PATH,PSK-PART,PSK-PARTSET")) (8 . "M-*水管*,M-*管道*")))
)
(defun psk-ss-getpipepath ()
  (ssget '((-3 ("PSK-PATH")) (8 . "M-*水管*,M-*管道*")))
)
(defun psk-comps-ssget ()
  (psk-ss->comps (ssget '((-3 ("PSK-PATH,PSK-PART,PSK-PARTSET,PSK-EQUIP")))))
)
(defun psk-comps-ssgetduct ()
  (psk-ss->comps (psk-ss-getduct))
)
(defun psk-comps-ssgetpipe ()
  (psk-ss->comps (psk-ss-getpipe))
)
(defun psk-comps-all ()
  (psk-ss->comps (ssget "X" '((-3 ("PSK-PATH,PSK-PART,PSK-PARTSET,PSK-EQUIP")))))
)
;;;(defun psk-comps-all ()
;;;  (setq ss (ssget "X" '((-3 ("PSK-PATH,PSK-PART,PSK-PARTSET,PSK-EQUIP")))))
;;;  (if (sslength ss) 1000)
;;;  (psk-ss->comps )
;;;)
(defun psk-comps-fromwindow (p1 p2)
  (psk-ss->comps (ssget "W" p1 p2 '((-3 ("PSK-PATH,PSK-PART,PSK-PARTSET,PSK-EQUIP")))))
)
(defun psk-comps-fromviewport ()
  (psk-comps-fromwindow
    (trans (getvar "EXTMIN") 0 1)
    (trans (getvar "EXTMAX") 0 1)
  )
)
(defun psk-paths-fromviewport ()
  (psk-ss->comps
    (ssget "W"
           (trans (getvar "EXTMIN") 0 1)
           (trans (getvar "EXTMAX") 0 1)
           '((-3 ("PSK-PATH")))
    )
  )
)
(defun psk-comps-fromviewport2 (layer)
  (psk-ss->comps
    (ssget "W"
	   (trans (getvar "EXTMIN") 0 1)
	   (trans (getvar "EXTMAX") 0 1)
	   (list '(-3 ("PSK-PATH,PSK-EQUIP")) (cons 8 (strcat (psk-get-customlayername "EQUIP") "," layer)))
    )
  )
)
;;;(defun psk-ss-paths (appid layer)
;;;  (setq filter (list (list -3 (list appid))))
;;;  (if layer
;;;    (setq filter (p-set filter (cons 8 layer)))
;;;  )
;;;
;;;  (ssget filter)
;;;)
