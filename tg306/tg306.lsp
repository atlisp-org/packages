;;;;;;;;;;;;;;;;;;;;;;;;;;;;;;;;;;;;;;;;;;;;;;;;;;;;;;;;;;;;;;;;;;;;;;;;;;;;;;;;
;; 这是使用开发工具 dev-tools 自动创建的程序源文件 
;;;;;;;;;;;;;;;;;;;;;;;;;;;;;;;;;;;;;;;;;;;;;;;;;;;;;;;;;;;;;;;;;;;;;;;;;;;;;;;;
;; 定义配置项 'tg306:first 用于 应用包 tg306 的 第一个配置项 first 
(@:define-config 'tg306:first "我是配置项 tg306:first 的值" "这个配置项的用途说明。")
;; (@:get-config 'tg306:first) ;; 获取配置顶的值
;; (@:set-config 'tg306:first  "新设的值") ;; 设置配置顶的值
;; 向系统中添加菜单 
(@:add-menu "钢连接框架" "高强螺栓排" "(tg306:menu-draw-gqls)" )
(@:add-menu "钢连接框架" "统计柱" "(tg306:stat-column)" )
(@:add-menu "钢连接框架" "统计梁" "(tg306:stat-beam)" )
(@:add-menu "钢连接框架" "绘预制梁" "(tg306:batch-draw-beam)" )
(@:add-menu "钢连接框架" "绘柱顶连接件" "(tg306:menu-draw-colutop)" )
(@:add-menu "钢连接框架" "标注板件" "(tg306:menu-dim-plate)" )

;; 绘螺栓
(defun tg306:draw-gqls(pt-base m dm n s / i j)
  "m 水平排数，dm 水平间距，n 竖向排数，s 竖向间距"
  (setq j 0)
  (repeat
   n
   (setq i 0)
   (repeat
    m
    (block:insert "高强螺栓孔" (@::get-config '@pm:tuku)
		  (polar
		   (polar pt-base (* 0.5 pi) (* j s))
		   0  (* i dm))
		  0 1)
    (setq i (1+ i)))
   (setq j (1+ j))))
(defun tg306:draw-ring-ls (pt-base m dm n s / i j)
  "m 水平排数，dm 水平间距，n 竖向排数，s 竖向间距"
  (setq j 0)
  (repeat
   n
   (setq i 0)
   (repeat
    m
    (if (or (= j 0)(= j (1- n))
	    (= i 0)(= i (1- m)))
	(block:insert "高强螺栓孔" (@::get-config '@pm:tuku)
		      (polar
		       (polar pt-base (* 0.5 pi) (* j s))
		       0  (* i dm))
		      0 1))
    (setq i (1+ i)))
   (setq j (1+ j))))
;;绘钢板
(defun tg306:make-steel-plate (pt-base b h t1)
  "绘制钢板:含厚度t1"
  (setq plate
	(entity:make-rectangle
	 (polar
	  (polar pt-base pi (* 0.5 b))
	  (* 1.5 pi)
	  (* 0.5 h))
	 (polar
	  (polar pt-base 0 (* 0.5 b))
	  (* 0.5 pi)
	  (* 0.5 h))
	 ))
  (entity:putdxf plate 39 t1)
  plate
  )

;; 绘梁连接件翼缘板elev
(defun tg306:draw-yyb (pt-base l w h po)
  "绘制翼缘板,l 长，w宽,h厚度，po:bool ,po 坡口角"
  (setq yyb
	(entity:make-lwpline-bold
	 (list pt-base
	       (polar pt-base 0 l)
	       (polar (polar pt-base 0 l) (* 0.5 pi) h)
	       (polar (polar pt-base 0 10) (* 0.5 pi) h));;45度坡口
	 nil 0 1 0))
  (entity:putdxf yyb 39  w))
(defun tg306:draw-fb (pt-base l w h )
  "绘制腹板,l 长，w宽,h厚度，po:bool ,是否打坡口"
  (setq fb
	(entity:make-lwpline-bold
	 (list (polar pt-base 0 35)
	       (setq pt-tmp (polar pt-base 0 l))
	       (setq pt-tmp (polar pt-tmp (* 0.5 pi) w))
	       (setq pt-tmp (polar pt-tmp  pi  (- l 35)))
	       (setq pt-tmp
		     (polar 
		      (polar pt-tmp  pi 35)
		      (* 1.5 pi) 35)
		     )
	       (setq pt-tmp (polar pt-tmp (* 1.5 pi) (- w 70))))
	 (list 0 0 0 -0.414 0 -0.414)
	 0 1 0))
  (entity:putdxf fb 39 h))
;; 绘梁连接件腹板elev
(defun tg306:draw-beam-joint  (pt-base height width ft yt d m dm n s l1 l2)
  "梁钢连接件,height 钢梁高，width,钢梁宽 yt 翼厚ft 腹厚，d m dm n s ：螺栓数据，l1，外露长度"
  (tg306:draw-yyb pt-base (+ l1 l2)  width yt (* 0.25 pi))
  (tg306:draw-yyb (polar pt-base (* 0.5 pi) (- height yt)) (+ l1 l2)  width yt (* 0.25 pi))
  (tg306:draw-fb
   (polar (polar pt-base 0 10)(* 0.5 pi)yt)
   (- (+ l1 l2) 10)
   (- height yt yt)
   ft)
  ;; 螺栓
  (tg306:draw-gqls (polar (polar pt-base 0 60) (* 0.5 pi) d)
		   m dm n s)
  ;;混凝土界线
  (entity:make-line
   (setq pt-tmp (polar pt-base 0 l1))
   (polar pt-tmp (* 0.5 pi) height))
  
  )

;;; 柱底
(defun tg306:column-bottom-joint (pt-base c-b c-h f-b f-h m dm n s square-bute-t / diff)
  (progn ;; 平面
    ;;法兰
    (setq diff (* 2 60))
    (tg306:make-rec-by-center pt-base (+ c-b diff)(+ c-h diff))
    ;; 方管
    (setq diff (* 2 -65))
    (tg306:make-rec-by-center pt-base (+ c-b diff)(+ c-h diff))
    (setq diff (* 2 -85))
    (tg306:make-rec-by-center pt-base (+ c-b diff)(+ c-h diff))
    ;; 螺栓劲板
    (setq diff 0)
    (tg306:draw-ring-ls 
     (polar
      (polar pt-base pi (+(* 0.5 c-b) diff))
      (* 1.5 pi)
      (+ (* 0.5 c-h) diff))
     m dm n s)
    ;; TODO: 劲板
    (setq pt-tmp
	  (polar pt-base pi (- (* 0.5 dm (1- m)) (* 0.5 dm)))
	  )
    (setq i 0)
    (repeat (1- m)
	    ;;上
	    (tg306:make-rec-by-center
	     (polar (polar pt-tmp 0 (* i dm))
		    (* 0.5 pi)
		    (- (* 0.5 c-h) 2.5))
	     20 125)
	    ;;下
	    (tg306:make-rec-by-center
	     (polar (polar pt-tmp 0 (* i dm))
		    (* 1.5 pi)
		    (- (* 0.5 c-h)2.5))
	     20 125)
	    (setq i (1+ i)))
    (setq pt-tmp
	  (polar pt-base (* 1.5 pi) (- (* 0.5 s (1- n)) (* 0.5 s)))
	  )
    (setq i 0)
    (repeat (1- n)
	    ;;左
	    (tg306:make-rec-by-center
	     (polar (polar pt-tmp (* 0.5 pi) (* i s))
		    pi
		    (- (* 0.5 c-b) 2.5))
	     125 20)
	    ;;右
	    (tg306:make-rec-by-center
	     (polar (polar pt-tmp (* 0.5 pi) (* i s))
		    0
		    (- (* 0.5 c-b) 2.5))
	     125 20)
	    (setq i (1+ i)))
    (progn ;; 标注
      ;; 水平
      (setq pt-hl
	    (polar 
	     (polar pt-base (* 1.5 pi) (+ 60 (* 0.5 c-h)))
	     pi (+ 60(* 0.5 c-b))))
      (setq pt-hr
	    (polar 
	     (polar pt-base (* 1.5 pi) (+ 60 (* 0.5 c-h)))
	     0 (+ 60(* 0.5 c-b))))
      (entity:dimhorizontal
       (setq pt-tmp(polar pt-hr pi 60))  pt-hr
       (polar (point:mid pt-tmp pt-hr) (* 1.5 pi) 120)
       )
      (entity:dimhorizontal
       pt-hl (setq pt-tmp (polar pt-hl 0 60))
       (polar (point:mid pt-hl pt-tmp) (* 1.5 pi) 120)
       )
      ;;总
      (entity:dimhorizontal
       pt-hl pt-hr
       (polar (point:mid pt-hl pt-hr) (* 1.5 pi) 200)
       )
      ;;螺栓
      (setq i  0)
      (repeat
       (1- m)
       (entity:dimhorizontal
	pt-tmp (setq pt-tmp2 (polar pt-tmp 0 dm))
	(polar (point:mid pt-tmp pt-tmp2) (* 1.5 pi) 120)
	)
       (setq pt-tmp pt-tmp2)
       (setq i (1+ i)))
      
      ;; 竖向
      (setq pt-vb
	    (polar 
	     (polar pt-base (* 1.5 pi) (+ 60 (* 0.5 c-h)))
	     pi (+ 60(* 0.5 c-b))))
      (setq pt-vt (polar pt-vb (* 0.5 pi) (+ c-h  60 60)))
      ;;总
      (entity:dimvertical
       pt-vb pt-vt
       (polar (point:mid pt-vb pt-vt) pi 200)
       )
      (entity:dimvertical
       (setq pt-tmp( polar pt-vt (* 1.5 pi) 60)) pt-vt
       (polar (point:mid pt-tmp pt-vt) pi 120)
       )
      (entity:dimvertical
       pt-vb (setq pt-tmp(polar pt-vb (* 0.5 pi) 60))
       (polar (point:mid pt-vb pt-tmp) pi 120)
       )
      ;;标螺栓
      (setq i  0)
      (repeat
       (1- n)
       (entity:dimvertical
	pt-tmp (setq pt-tmp2 (polar pt-tmp (* 0.5 pi) s))
	(polar (point:mid pt-tmp pt-tmp2) pi 120)
	)
       (setq pt-tmp pt-tmp2)
       (setq i (1+ i)))
      
      )
    )
  (progn  ;;; 正立面
    (setq pt-front (polar pt-base (* 0.5 pi) (* 1.5 c-h)))
    (entity:make-point pt-front)
    ;;底板
    (tg306:make-rec-by-center
     (polar pt-front (* 0.5 pi) 15)
     (+ c-b 120) 30)
    (entity:putdxf 
     (tg306:make-rec-by-center
      (polar pt-front (* 1.5 pi) 15)
      (+ c-b 120) 30)
     62 252)

    
    ;;方管
    (tg306:make-rec-by-center
     (polar pt-front (* 0.5 pi) (+ 30 (* 0.5 (+ 200(* 0.5  (max c-b c-h))))))
     (+ c-b -130) (+ 200 (* 0.5 (max c-b c-h))))
    (tg306:make-rec-by-center
     (polar pt-front (* 0.5 pi) (+ 30 (* 0.5 (+ 200 (* 0.5 (max c-b c-h))))))
     (+ c-b (- -130 (* 2 square-bute-t))) (+ 200 (* 0.5 (max c-b c-h))))
    ;; 螺栓
    (setq pt-tmp (polar pt-front pi (* 0.5 (1- m) dm)))
    (setq i 0)
    (repeat m
	    (block:insert "螺栓立面" (@::get-config '@pm:tuku) (polar pt-tmp 0 (* i dm)) 0 1)
	    (setq i (1+ i)))
    ;;劲板
    (setq pt-tmp
	  (polar pt-front pi (- (* 0.5 dm (1- m)) (* 0.5 dm)))
	  )
    (setq i 0)
    (repeat (1- m)
	    ;;上
	    (tg306:make-rec-by-center
	     (polar (polar pt-tmp 0 (* i dm))
		    (* 0.5 pi)
		    80)
	     20 100)
	    ;;下
	    (entity:putdxf 
	     (tg306:make-rec-by-center
	      (polar (polar pt-tmp 0 (* i dm))
		     (* 1.5 pi)
		     105)
	      20 150)
	     62 252)
	    (setq i (1+ i)))
    )

  (progn ;;; 侧立面
    (setq pt-left
	  (polar 
	   (polar pt-base 0 (+ (* 1.5 c-b) c-h))
	   (* 1.5 pi)
	   (* 0.5 c-h )))
    
    (entity:make-point pt-left)
    ;;底板
    (tg306:make-rec-by-center
     (polar pt-left (* 0.5 pi) 15)
     (+ c-h 120) 30)
    (entity:putdxf 
     (tg306:make-rec-by-center
      (polar pt-left (* 1.5 pi) 15)
      (+ c-h 120) 30)
     62 252)
    ;;方管
    (tg306:make-rec-by-center
     (polar pt-left (* 0.5 pi) (+ 30 (* 0.5 (+ 200(* 0.5  (max c-b c-h))))))
     (+ c-h -130) (+ 200 (* 0.5 (max c-b c-h))))
    (tg306:make-rec-by-center
     (polar pt-left (* 0.5 pi) (+ 30 (* 0.5 (+ 200 (* 0.5 (max c-b c-h))))))
     (+ c-h (- -130 (* 2 square-bute-t))) (+ 200 (* 0.5 (max c-b c-h))))

    ;; 螺栓
    (setq pt-tmp (polar pt-left pi (* 0.5 (1- n) s)))
    (setq i 0)
    (repeat n
	    (block:insert "螺栓立面" (@::get-config '@pm:tuku) (polar pt-tmp 0 (* i s)) 0 1)
	    (setq i (1+ i)))
    ;;劲板
    (setq pt-tmp
	  (polar pt-left pi (- (* 0.5 s (1- n)) (* 0.5 s)))
	  )
    (setq i 0)
    (repeat (1- n)
	    ;;上
	    (tg306:make-rec-by-center
	     (polar (polar pt-tmp 0 (* i s))
		    (* 0.5 pi)
		    80)
	     20 100)
	    ;;下
	    (entity:putdxf
	     (tg306:make-rec-by-center
	      (polar (polar pt-tmp 0 (* i s))
		     (* 1.5 pi)
		     105)
	      20 150)
	     62 252)
	    (setq i (1+ i)))
    )
  
  )

;;; 柱顶连接件
(defun tg306:column-top-elev (pt-front c-b m dm max-bh)
  "c-b 柱宽/高，m 螺栓排数，dm间距"
  (entity:make-point pt-front)
  (progn ;;顶板
      (tg306:make-steel-plate 
       (polar pt-front (* 1.5 pi) 15)
       (+ c-b 120) 30
       (+ c-h 120)
       )
      (entity:putdxf ;;上柱板
       (tg306:make-steel-plate
	(polar pt-front (* 0.5 pi) 15)
	(+ c-b 120) 30
	(+ c-h 120)
	)
       62 252))
  (progn ;;方管 ，两段，由贯通板隔开
      (tg306:make-steel-plate
       (polar pt-front
	      (* 1.5 pi)
	      (+ 30 (* 0.5 (- max-bh 120 50))))
       (+ c-b -130)
       (- max-bh 120 20 30) ;; joint-h
       20
       )
      (tg306:make-steel-plate
       (polar pt-front
	      (* 1.5 pi)
	      (+ 30 (* 0.5 (- max-bh 120  50))))
       (+ c-b (- -130 (* 2 square-bute-t)))
       (- max-bh 120 20 30) ;; joint-h
       20)
      ;;下方管
      (tg306:make-steel-plate
       (polar pt-front
	      (* 1.5 pi)
	      (+ max-bh -120 (* 0.5 (- joint-h max-bh -120))))
       (+ c-b -130)
       (- joint-h max-bh -120)
       20
       )
      (tg306:make-steel-plate
       (polar pt-front
	      (* 1.5 pi)
	      (+ max-bh -120 (* 0.5 (- joint-h max-bh -120))))
       (+ c-b (- -130 (* 2 square-bute-t)))
       (- joint-h max-bh -120)
       20)
      
  
      ;; (tg306:make-steel-plate
      ;;  (polar pt-front
      ;; 	      (* 1.5 pi)
      ;; 	      (+ 30 (* 0.5 joint-h)))
      ;;  (+ c-b (- -130 (* 2 square-bute-t)))
      ;;  joint-h
      ;;  20)
      )
  (progn ;; 螺栓劲板
      (setq pt-tmp (polar pt-front pi (* 0.5 (1- m) dm)))
      (setq i 0)
      (repeat m
	      (block:insert "螺栓立面" (@::get-config '@pm:tuku) (polar pt-tmp 0 (* i dm)) 0 1)
	      (setq i (1+ i)))
      ;;劲板
      (setq pt-tmp
	    (polar pt-front pi (- (* 0.5 dm (1- m)) (* 0.5 dm)))
	    )
      (setq i 0)
      (repeat (1- m)
	      ;;上
	      ;; (entity:putdxf 
	      ;;  (tg306:make-rec-by-center
	      ;;   (polar (polar pt-tmp 0 (* i dm))
	      ;; 	     (* 0.5 pi)
	      ;; 	     80)
	      ;;   20 100)
	      ;;  62 252)
	      ;;下
	      (tg306:make-steel-plate
	       (polar (polar pt-tmp 0 (* i dm))
		      (* 1.5 pi)
		      105)
	       20 150
	       125)
	      (setq i (1+ i))))
  (progn ;;梁底接板，贯通板，同环板，再外接梁底翼缘板（同梁翼缘宽）
      (tg306:make-steel-plate
       (setq pt-tmp (polar pt-front (* 1.5 pi) (- max-bh 120 10)))
       (+ c-b 120) 20
       (+ c-h 120)
       )
      
      ;; 梁腹接板，需读梁中位置及梁腹厚度，如与螺栓冲突，
      (setq hf 430
	    l1 305 )
      
      (tg306:column-top-beam
       (polar 
	(polar pt-front (* 1.5 pi) 30)
	0 (- (* 0.5 c-b) 65))
       hf l1 nil)
      (tg306:column-top-beam
       (polar 
	(polar pt-front (* 1.5 pi) 30)
	pi (- (* 0.5 c-b) 65))
       hf l1 t)
      )
  
  (progn ;; 环板
      (tg306:make-steel-plate
       (polar pt-front (* 1.5 pi) (+ max-bh -120 260 10))
       (- c-b 40) 20
       (- c-h 40)
       )
      )
  (progn ;;标柱
      (setq pt-vt (polar pt-front 0 (+ (* 0.5 c-b) 400)))
      (setq pt-vb (polar pt-vt (* 1.5 pi) (+ joint-h 0)))
      ;;总
      (entity:dimvertical
       pt-vt pt-vb
       (polar (point:mid pt-vb pt-vt) 0 280)
       )
      (entity:dimvertical
       pt-vt
       (setq pt-tmp (polar pt-vt (* 1.5 pi) (- max-bh 120)))
       (polar (point:mid pt-tmp pt-vt) 0 200)
       )
      (entity:dimvertical
       pt-tmp
       (setq pt-tmp1 (polar pt-tmp (* 1.5 pi ) 260))
       (polar (point:mid pt-tmp1 pt-tmp ) 0 200)
       )
      (entity:dimvertical
       pt-tmp1
       (setq pt-tmp (polar pt-tmp1 (* 1.5 pi ) 20))
       (polar (point:mid pt-tmp1 pt-tmp ) 0 200)
       )
      (entity:dimvertical
       pt-tmp pt-vb
       (polar (point:mid pt-vb pt-tmp ) 0 200)
       )
      )
  )
(defun tg306:column-top-beam (pt-base hf l1 mirrorp)
  (setq l1 (- l1 50))
  (setq pts
	(list (list 0 0)
	      (list 0 (* -1 hf))
	      (list 125 0)
	      (list 0 30) ;; 不是50 
	      (list l1 0)
	      (list 0 (- hf 50))
	      (list (* -1 l1) 0)
	      (list 0 20)))
  (if mirrorp
      (setq pts
	    (mapcar '(lambda(x)
		       (mapcar '* '(-1 1 1)
			       x))
		    pts)))
	  
  (setq lwpts nil)
  (setq pt-tmp pt-base)
  (foreach pt pts
	   (print pt)
	   (setq lwpts
		 (cons (setq pt-tmp
			     (mapcar '+
				     pt-tmp pt))
		       lwpts)))
  (print lwpts)
  (entity:make-lwpolyline lwpts nil 0 1 0)
  
  )
(defun tg306:get-beam-h(colu) ;;柱周最大梁高
  "取柱周梁的最大高度"
  600 ;;应该取梁高最大值这里先按800
  )

(defun tg306:column-top-joint (pt-base c-b c-h f-b f-h m dm n s square-bute-t max-bh / diff)
  "max-bh: 柱周最大梁高"
  (setq dim-offset 300 ;;标注偏移量
	joint-h (+ 260 max-bh -120 (* 0.5 (- (max c-b c-h) 124))));;钢件总高度
  (progn ;; 平面
    ;;法兰
    (setq diff (* 2 60))
    (setq plate-tmp
	  (tg306:make-steel-plate pt-base (+ c-b diff) (+ c-h diff) 30))
    (tg306:dim-plate plate-tmp)
    ;;键孔
    (setq plate-tmp
	  (tg306:make-steel-plate pt-base 250 250 30))
    ;;; 方管
    ;;上
    (setq diff (* 2 -65))
    (setq plate-tmp
	  (tg306:make-steel-plate
	   (polar pt-base (* 0.5 pi) (+ (* 0.5 (+ c-h diff)) -10))
	   (+ c-b diff) 20 (- joint-h 30)))
    (tg306:dim-plate plate-tmp)
    ;;下
    (setq diff (* 2 -65))
    (setq plate-tmp
	  (tg306:make-steel-plate
	   (polar pt-base (* 1.5 pi) (+ (* 0.5 (+ c-h diff)) -10))
	   (+ c-b diff) 20 (- joint-h 30)))
   ;;左
    (setq diff (* 2 -65))
    (setq plate-tmp
	  (tg306:make-steel-plate
	   (polar pt-base pi (+ (* 0.5 (+ c-b diff)) -10))
	   20 (+ c-h diff -40) (- joint-h 30)))
    (tg306:dim-plate plate-tmp)
    ;;右
    (setq diff (* 2 -65))
    (setq plate-tmp
	  (tg306:make-steel-plate
	   (polar pt-base 0 (+ (* 0.5 (+ c-b diff)) -10))
	   20 (+ c-h diff -40) (- joint-h 30)))
    (progn;; 螺栓劲板
      (setq diff 0)
      (tg306:draw-ring-ls 
       (polar
	(polar pt-base pi (+(* 0.5 c-b) diff))
	(* 1.5 pi)
	(+ (* 0.5 c-h) diff))
       m dm n s)
      ;;  劲板
      (setq pt-tmp
	    (polar pt-base pi (- (* 0.5 dm (1- m)) (* 0.5 dm)))
	    )
      (setq i 0)
      (repeat (1- m)
	      ;;上
	      (setq plate-tmp
	      (tg306:make-steel-plate
	       (polar (polar pt-tmp 0 (* i dm))
		      (* 0.5 pi)
		      (- (* 0.5 c-h) 2.5))
	       12 125 150))
	      (if (= i 0)
		  (tg306:dim-plate plate-tmp))
	      ;;下
	      (tg306:make-steel-plate
	       (polar (polar pt-tmp 0 (* i dm))
		      (* 1.5 pi)
		      (- (* 0.5 c-h)2.5))
	       12 125 150)
	      (setq i (1+ i)))
      (setq pt-tmp
	    (polar pt-base (* 1.5 pi) (- (* 0.5 s (1- n)) (* 0.5 s)))
	    )
      (setq i 0)
      (repeat (1- n)
	      ;;左
	      (tg306:make-steel-plate
	       (polar (polar pt-tmp (* 0.5 pi) (* i s))
		      pi
		      (- (* 0.5 c-b) 2.5))
	       125 12 150)
	      ;;右
	      (setq plate-tmp  
	      (tg306:make-steel-plate
	       (polar (polar pt-tmp (* 0.5 pi) (* i s))
		      0
		      (- (* 0.5 c-b) 2.5))
	       125 12 150))
	      (if (= i 0)
		  (tg306:dim-plate plate-tmp))
	      (setq i (1+ i)))
      )
    (progn ;; 标注
      ;; 水平
      (setq pt-hl
	    (polar 
	     (polar pt-base (* 1.5 pi) (+ 150 (* 0.5 c-h)))
	     pi (+ 60(* 0.5 c-b))))
      (setq pt-hr
	    (polar 
	     (polar pt-base (* 1.5 pi) (+ 150 (* 0.5 c-h)))
	     0 (+ 60(* 0.5 c-b))))
      (entity:dimhorizontal
       (setq pt-tmp(polar pt-hr pi 60))  pt-hr
       (polar (point:mid pt-tmp pt-hr) (* 1.5 pi) dim-offset)
       )
      (entity:dimhorizontal
       pt-hl (setq pt-tmp (polar pt-hl 0 60))
       (polar (point:mid pt-hl pt-tmp) (* 1.5 pi) dim-offset)
       )
      ;;总
      (entity:dimhorizontal
       pt-hl pt-hr
       (polar (point:mid pt-hl pt-hr) (* 1.5 pi) (+ 80  dim-offset))
       )
      ;;螺栓
      (setq i  0)
      (repeat
       (1- m)
       (entity:dimhorizontal
	pt-tmp (setq pt-tmp2 (polar pt-tmp 0 dm))
	(polar (point:mid pt-tmp pt-tmp2) (* 1.5 pi) dim-offset)
	)
       (setq pt-tmp pt-tmp2)
       (setq i (1+ i)))
      
      ;; 竖向
      (setq pt-vb
	    (polar 
	     (polar pt-base (* 1.5 pi) (+ 60 (* 0.5 c-h)))
	     pi (+ 60(* 0.5 c-b))))
      (setq pt-vt (polar pt-vb (* 0.5 pi) (+ c-h  60 60)))
      ;;总
      (entity:dimvertical
       pt-vb pt-vt
       (polar (point:mid pt-vb pt-vt) pi (+ 80 dim-offset))
       )
      (entity:dimvertical
       (setq pt-tmp( polar pt-vt (* 1.5 pi) 60)) pt-vt
       (polar (point:mid pt-tmp pt-vt) pi dim-offset)
       )
      (entity:dimvertical
       pt-vb (setq pt-tmp(polar pt-vb (* 0.5 pi) 60))
       (polar (point:mid pt-vb pt-tmp) pi dim-offset)
       )
      ;;标螺栓
      (setq i  0)
      (repeat
       (1- n)
       (entity:dimvertical
	pt-tmp (setq pt-tmp2 (polar pt-tmp (* 0.5 pi) s))
	(polar (point:mid pt-tmp pt-tmp2) pi dim-offset)
	)
       (setq pt-tmp pt-tmp2)
       (setq i (1+ i)))
      
      )
    )
  (progn  ;;; 立面
    (setq pt-front (polar pt-base (* 1.5 pi) 1200 ))
    (tg306:column-top-elev pt-front c-b m dm max-bh)
    (setq pt-left
	  (polar 
	   (polar pt-base 0 (+ (* 1.5 c-b) c-h))
	   (* 0.5 pi)
	   (* 0.5 c-h)))
    (tg306:column-top-elev pt-left c-h n s max-bh))

  )
(defun tg306:get-beam-joint-info (b  h / info)
  (setq info (assoc (strcat "矩"(itoa (fix b))"x"(itoa(fix h))) build1-beam))
  (setq joint-info (string:to-list  (substr (cadr info) 3)"x"))
  (setq height (read (car joint-info)))
  (setq width  (read (cadr joint-info)))
  (setq ft  (read (caddr joint-info)))
  (setq yt  (read (last joint-info)))
  (setq d (nth 3 info)
	n (1+ (nth 2 info))
	dm 70
	m (nth 4 info)
	s (nth 5 info)
	l1 (nth 6 info)
	l2 300)
  )
(defun tg306:get-columntop-joint-para (ct-list)
  (setq bxh
	(string:to-list (string:l2s-ansi (cdr (string:s2l-ansi (car ct-list))))"x"))
  (setq f-bxh 	(string:to-list (cadr ct-list)"x"))
  (setq c-b (read (car bxh))
	c-h (read(cadr bxh))
	f-b (read(car f-bxh))
	f-h (read(cadr f-bxh))
	m (1+ (read(nth 2 ct-list)))
	dm (read(nth 3  ct-list))
	n (1+ (read(nth 4 ct-list)))
	s (read(nth 5 ct-list))
	bute-t 20)
  (list c-b c-h f-b f-h m dm n s bute-t)
  )
(defun tg306:beam-info (beam-ent)
  "梁信息，宽高，连接件信息"
  (list
   (cons 10 (entity:getdxf beam-ent))
   (cons 'b (block:get-dynprop beamblk "宽"))
   (cons 'h (cdr (assoc "高" (block:get-attributes beam-ent))))
   (cons 'joint 0)))
(defun tg306:column-beam-bottom-plate (pt c-b c-h beam4-info)

  )
(defun tg306:draw-column (columnblk floor-h)
 "绘制柱构件图 floor-h"
  ;; 从梁宽高和连接表中取连接件信息
  (princ (strcat "\n绘制" (cdr (assoc "编号" (block:get-attributes columnblk)))))
  (setq c-b (block:get-dynprop columnblk "b"))
  (setq c-h (block:get-dynprop columnblk "h"))
  (setq mark-length  (block:get-dynprop beamblk "标志长度"))
  (tg306:get-beam-joint-info b-b b-h)
  ;;图框
  (setq tk (tg306:insert-frame
	    "图框-好逐易工程服务"
	    (polar 
	     (polar pt-base 0
		    (cond
		     ((<= mark-length 4700) 5510)
		     ((< 4700 mark-length 6200) 7000)
		     ((>= mark-length 6200) 8480))
		    )
	     (* 1.5 pi) 3600)
	    (cond
	     ((<= mark-length 4700)"A2")
	     ((< 4700 mark-length 6200) "A2+0.25")
	     ((>= mark-length 6200) "A2+0.5"))
	    (cdr (assoc "编号" (block:get-attributes beamblk)))
	    ))
  ;; 底接头
  (tg306:column-bottom-joint
   (polar (polar pt-base 0 65)
	  (* 1.5 pi) (- b-h 60))
   height width ft yt d m dm n s l1 l2)
  ;;混
  (setq beam-ent
	(block:insert "预制柱-混立" (@::get-config '@pm:tuku)
		      (polar pt-base 0 (+ 60 l1)) 0 1))
  (block:set-dynprop beam-ent "h" b-h)
  ;;;标注
  ;;;标志长度
  (entity:dimhorizontal
   pt-base
   (setq pt-tmp (polar pt-base 0 (block:get-dynprop beamblk "标志长度")))
   (polar (point:mid pt-base pt-tmp) (* 1.5 pi) (+ b-h 300))
   )
  ;; 柱翼接点长度
  (setq pt-b-base (polar pt-base(* 1.5 pi) b-h))
  (entity:dimhorizontal
   pt-b-base
   (setq pt-tmp (polar pt-b-base 0  60))
   (polar (point:mid pt-b-base pt-tmp) (* 1.5 pi) 200)
   )
   ;; 柱翼接点长度
  (entity:dimhorizontal
   pt-tmp
   (setq pt-tmp1 (polar pt-tmp 0 5))
   (polar (point:mid pt-tmp pt-tmp1) (* 1.5 pi) 200)
   )
  ;; 梁L1-5
  (entity:dimhorizontal
   pt-tmp1
   (setq pt-tmp (polar pt-tmp1 0 (- l1 5)))
  (polar (point:mid pt-tmp pt-tmp1) (* 1.5 pi) 200)
  )
  ;; 混凝土
  (entity:dimhorizontal
   pt-tmp
   (setq pt-tmp1 (polar
		  pt-tmp 0
		  (- (block:get-dynprop beamblk "标志长度")
		    (* 2 (+ 60 l1)))))
   (polar (point:mid pt-tmp pt-tmp1) (* 1.5 pi) 200)
  )
  (princ "..OK")
  ;;返回下一个图的绘制基点
  (polar pt-base 0
	 (cond
	  ((<= mark-length 4700) 6110)
	  ((< 4700 mark-length 6200) 7600)
	  ((>= mark-length 6200) 9080))
	 )

  )
;;需读取四边梁数据
(defun tg306:column-beam-relation (columnblk / b h base beams)
  (setq b (fix(block:get-dynprop columnblk "b"))
	h (fix(block:get-dynprop columnblk "h")))
  (setq base  (entity:getdxf columnblk 10))
  (setq beams
	(pickset:to-list
	 (block:ssget
	  (list "c"
		(mapcar '+
			(list (+ 10 b) (+ 10 h))
			base)
		(mapcar '-
			base
			(list (+ 10 b) (+ 10 h))
			))
	  "beam-yz" nil)
	 ))
  (setq beam-offset '((1)(2)(3)(4)))
  (foreach
   beam beams
   (setq beam-o (entity:getdxf beam 10))
   (cond
	      ((and (equal
		     (car base)
		     (car beam-o)
		     (* 0.49 b))
		    (> (cadr base)
		       (cadr beam-o)))
	       (setq beam-offset
		     (subst (cons 1
				  (fix (- (car base)(car beam-o))))
			    (assoc 1 beam-offset)
			    beam-offset)))
	      ((and (equal
		     (car base)
		     (car beam-o)
		     (* 0.49 b))
		    (< (cadr base)
		       (cadr beam-o)))
	       (setq beam-offset
		     (subst (cons 3
				  (fix (- (car base)(car beam-o))))
			    (assoc 3 beam-offset)
			    beam-offset)))
	      ((and (equal
		     (cadr base)
		     (cadr beam-o)
		     (* 0.49 h))
		    (> (car base)
		       (car beam-o)))
	       (setq beam-offset
		     (subst (cons 4
				  (fix(- (cadr base)(cadr beam-o))))
			    (assoc 4 beam-offset)
			    beam-offset)))
	      ((and (equal
		     (cadr base)
		     (cadr beam-o)
		     (* 0.49 h))
		    (< (car base)
		       (car beam-o)))
	       (setq beam-offset
		     (subst (cons 2
				 (fix (- (cadr base)(cadr beam-o))))
			    (assoc 2 beam-offset)
			    beam-offset))))
   )
  (list
   b h
   (mapcar 'cdr beam-offset)
   ))

;;; 绘制梁
(defun tg306:draw-beam (beamblk pt-base / b-b b-h)
  "绘制梁构件图"
  ;; 从梁宽高和连接表中取连接件信息
  (princ (strcat "\n绘制" (cdr (assoc "编号" (block:get-attributes beamblk)))))
  (setq b-b (block:get-dynprop beamblk "宽"))
  (setq b-h (read (cdr (assoc "高" (block:get-attributes beamblk)))))
  (setq mark-length  (block:get-dynprop beamblk "标志长度"))
  (tg306:get-beam-joint-info b-b b-h)
  ;;图框
  (setq tk (tg306:insert-frame
	    "图框-好逐易工程服务"
	    (polar 
	     (polar pt-base 0
		    (cond
		     ((<= mark-length 4700) 5510)
		     ((< 4700 mark-length 6200) 7000)
		     ((>= mark-length 6200) 8480))
		    )
	     (* 1.5 pi) 3600)
	    (cond
	     ((<= mark-length 4700)"A2")
	     ((< 4700 mark-length 6200) "A2+0.25")
	     ((>= mark-length 6200) "A2+0.5"))
	    (cdr (assoc "编号" (block:get-attributes beamblk)))
	    ))
  ;; 左接头
  (tg306:draw-beam-joint
   (polar (polar pt-base 0 65)
	  (* 1.5 pi) (- b-h 60))
   height width ft yt d m dm n s l1 l2)
  ;;混
  (setq beam-ent
	(block:insert "预制梁-混立" (@::get-config '@pm:tuku)
		      (polar pt-base 0 (+ 60 l1)) 0 1))
  (block:set-dynprop beam-ent "h" b-h)
  ;;;标注
  ;;;标志长度
  (entity:dimhorizontal
   pt-base
   (setq pt-tmp (polar pt-base 0 (block:get-dynprop beamblk "标志长度")))
   (polar (point:mid pt-base pt-tmp) (* 1.5 pi) (+ b-h 300))
   )
  ;; 柱翼接点长度
  (setq pt-b-base (polar pt-base(* 1.5 pi) b-h))
  (entity:dimhorizontal
   pt-b-base
   (setq pt-tmp (polar pt-b-base 0  60))
   (polar (point:mid pt-b-base pt-tmp) (* 1.5 pi) 200)
   )
   ;; 柱翼接点长度
  (entity:dimhorizontal
   pt-tmp
   (setq pt-tmp1 (polar pt-tmp 0 5))
   (polar (point:mid pt-tmp pt-tmp1) (* 1.5 pi) 200)
   )
  ;; 梁L1-5
  (entity:dimhorizontal
   pt-tmp1
   (setq pt-tmp (polar pt-tmp1 0 (- l1 5)))
  (polar (point:mid pt-tmp pt-tmp1) (* 1.5 pi) 200)
  )
  ;; 混凝土
  (entity:dimhorizontal
   pt-tmp
   (setq pt-tmp1 (polar
		  pt-tmp 0
		  (- (block:get-dynprop beamblk "标志长度")
		    (* 2 (+ 60 l1)))))
   (polar (point:mid pt-tmp pt-tmp1) (* 1.5 pi) 200)
  )
  (princ "..OK")
  ;;返回下一个图的绘制基点
  (polar pt-base 0
	 (cond
	  ((<= mark-length 4700) 6110)
	  ((< 4700 mark-length 6200) 7600)
	  ((>= mark-length 6200) 9080))
	 )
  )

(setq build1-beam
      (list
       '("矩250x450" "WH330x190x10x14" 1 130 2 70 235)
       '("矩250x600" "WH480x190x14x16" 4 100 5 70 445)
       '("矩300x600" "WH480x240x10x16" 4 100 3 70 305)
       '("矩350x600" "WH480x290x10x16" 4 100 3 70 305)
       '("矩250x500" "WH380x190x8x14" 2 100 2 100 305)
       '("矩200x400" "WH280x140x6x8" 1 100 2 90 305)))     
(defun tg306:get-list-from-texts()
  (setq txts
	(pickset:sort 
	 (pickset:to-list (ssget  '((0 . "text"))))
	 "Yx"
	 '(100 100)))
  (mapcar 'tg306:get-columntop-joint-para
	  (list:split (mapcar 'text:get-mtext  txts) 7))
  )

;;;引线标注板尺寸
(defun tg306:dim-plate (plate / box bh)
  ;; box  中已包含厚度
  (setq box (entity:getbox plate 0))
  (setq bh (mapcar '- (cadr box)(car box)))
  (if (< (car bh) 35)
      (setq  bh (list (cadr bh)(car bh)(caddr bh))))
  (if (< (caddr bh) 35)
      (setq  bh (list (car bh)(caddr bh)(cadr bh))))
  (entity:make-multileader (list (cadr box)
				 (polar (cadr box) (* 0.25 pi) 200))
			   (strcat (itoa (fix(car bh)))"x"(itoa (fix(cadr bh)))
				   "\n"(itoa (fix (caddr bh))))))

;;插图框
(defun tg306:insert-frame (frame-name pt map  draw-name)
  ;;图框
  (setq tk 
	(block:insert frame-name (@::get-config '@pm:tuku)
		      pt  
		      0 0.1))
  (block:set-dynprop tk "map-sheet" map)
  (block:set-attributes tk (list  (cons "图名"  draw-name )))
  tk)

;;; menu 
(defun tg306:stat-beam()
  "统计梁类型并回写编号"
  (setq beams
	(pickset:sort 
	 (pickset:to-list (block:ssget nil "beam-yz" nil))
	 "xy" 10)
	)
  (setq lst
	(stat:stat
	(mapcar
	 '(lambda(beamblk)
	    (list
	     ;; (cdr (assoc "编号" (block:get-attributes beamblk)))
	     (fix (block:get-dynprop beamblk "标志长度"))
	     (fix (block:get-dynprop beamblk "宽"))
	     (cdr (assoc "高" (block:get-attributes beamblk)))
	     (cdr (assoc "设计号" (block:get-attributes beamblk))))
	    )
	 beams)))
  ;;绘表格
  (setq i 0)
  (setq lst (mapcar '(lambda(x)
		       (setq i (1+ i))
		       (setq bh  (strcat "L-F0-" (string:number-format
					       (itoa i)
					       2 0 "00")))
		       ;;回写
		       (mapcar
			'(lambda(beamblk)
			   (if 
			       (list:equal
				(list
				 (fix (block:get-dynprop beamblk "标志长度"))
				 (fix (block:get-dynprop beamblk "宽"))
				 (cdr (assoc "高" (block:get-attributes beamblk)))
				 (cdr (assoc "设计号" (block:get-attributes beamblk))))
				(car x)
				0.1)
			       (block:set-attributes beamblk (list (cons "编号" bh)))
			     ))
			beams)
		       (append
			(list i)
			(list bh)
			(car x)
			(list (cdr x))
			))
		    lst))
  (print lst)
  (table:make (getpoint) "梁信息表" '("序号""编号""标志长度""宽""高""设计号""个数")
	      lst)
			      
  )
(defun tg306:stat-column()
  "统计柱，含与柱相连的梁信息"
  (setq columns
	(pickset:sort 
	 (pickset:to-list (block:ssget nil "柱" nil))
	 "xy" 10)
	)
  (setq lst
	(stat:stat
	(mapcar
	 '(lambda(columnblk )
	    (tg306:column-beam-relation columnblk)
	    )
	 columns)))
  (print lst)
  (setq i 0)
  (setq lst (mapcar '(lambda(x / bh)
		       (setq i (1+ i))
		       (setq bh  (strcat "Z-F0-" (string:number-format
					       (itoa i)
					       2 0 "00")))
		       回写
		       (mapcar
			'(lambda(columnblk)
			   (if 
			       (list:equal
				(tg306:column-beam-relation columnblk)
				(car x)
				0.01)
			       (block:set-attributes columnblk (list (cons "编号" bh)))
			     ))
			columns)
		       (append
			(list i)
			(list bh)
			(list (car (car x)))
			(list (cadr (car x)))
			(list 
			 (string:from-list
			  (mapcar '(lambda(y)
				     (if (null y)
					 "#"
				       (@:to-string y)))
				  (caddr (car x)))
			  "|"))
			(list (cdr x))
			))
		    lst))
  (table:make (getpoint) "柱信息表" '("序号""编号""宽""高""梁关系""个数")
	      lst)
	
  )
(defun tg306:batch-draw-beam ()
  (setq beams
	(pickset:sort 
	 (pickset:to-list (block:ssget nil "beam-yz" nil))
	 "xy" 10)
	)
  (setq pt-base (getpoint))
  (setq i 0)
  (setq nums nil)
  (foreach beam beams
	   ;;跳过已有编号的块
	   (if(null (member (cdr (assoc "编号" (block:get-attributes beam )))nums))
	       (progn
		 (setq nums (cons (cdr (assoc "编号" (block:get-attributes beam)))nums))
		 (setq pt-base (tg306:draw-beam beam pt-base))
		 )))
  )
(defun tg306:menu-draw-colutop ()
  (setq ctop-lst (tg306:get-list-from-texts))
  (setq pt-base (getpoint))
  (foreach ctop ctop-lst
	   (apply 'tg306:column-top-joint
		  (append (list  pt-base)  ctop (list 600)))
	   ;;插图框
	   ;;图框
	   (setq tk (tg306:insert-frame
		     "图框-好逐易工程服务"
		     (polar 
		      (polar pt-base 0 4800)
		      (* 1.5 pi) 3300)
		     "A2"
		     (strcat "矩" (itoa (car ctop))"x"(itoa(cadr ctop)))
		     ))
	   
	   (setq pt-base (polar pt-base 0 8000))
	   )
  
  )
(defun tg306:menu-draw-gqls ()
  (setq m  (getint "水平排数: "))
  (setq dm  (getreal "水平间距: "))
  (setq n  (getint "竖向排数: "))
  (setq s  (getreal "竖向间距: "))
  (tg306:draw-gqls (getpoint "初始点: ") m dm n s))

(defun tg306:menu-dim-plate ()
  (mapcar 'tg306:dim-plate
	  (pickset:to-list (ssget  '((0 . "lwpolyline"))))))
